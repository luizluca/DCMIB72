-------------------------------------------------------------------------------
--
-- Title: Systems Management Field Replaceable Unit (FRU) MIB
--
-- Version: 5.6.0
--
-- Release Date: April 2006
--
-- Description: This MIB defines MIB objects that make system FRU
-- information available to SNMP management applications.
--
-- Copyright (c) 2000-2006 Dell Inc.
-- All Rights Reserved.
--
-- Note: The information and functionality described by this MIB file,
-- like many MIB files, is subject to change without notice.
-- Please examine the version number of this MIB and compare it
-- to the version number you are expecting.
--
-- OID Format Legend:
--   <a> = attribute ID
--   <i> = index ID
--
-------------------------------------------------------------------------------


-------------------------------------------------------------------------------
-- Begin MIB
-------------------------------------------------------------------------------

DCS3FRU-MIB DEFINITIONS ::= BEGIN

IMPORTS
    enterprises, Gauge
        FROM RFC1155-SMI
    OBJECT-TYPE
        FROM RFC-1212
    DisplayString
        FROM RFC1213-MIB;


-------------------------------------------------------------------------------
-- Object Identifiers
-------------------------------------------------------------------------------

-- Enterprise ID
dell                            OBJECT IDENTIFIER ::= { enterprises    674   }

-- Server3 Branch
server3                         OBJECT IDENTIFIER ::= { dell           10892 }

-- Server3 Groups
baseboardGroup                  OBJECT IDENTIFIER ::= { server3        1     }

-- Server3 Baseboard Groups for FRU
-- (Other Server3 Baseboard groups are defined in other MIB files.)
fruGroup                        OBJECT IDENTIFIER ::= { baseboardGroup 2000  }


-------------------------------------------------------------------------------
-- Textual Conventions
-------------------------------------------------------------------------------

DellObjectRange                 ::= INTEGER (1..128)
DellUnsigned8BitRange           ::= INTEGER (0..255)
DellUnsigned16BitRange          ::= INTEGER (0..65535)
DellUnsigned32BitRange          ::= Gauge   (0..4294967295)

-- DellDateName dates are defined in the displayable format
--   yyyymmddHHMMSS.uuuuuu+ooo
-- where yyyy is the year, mm is the month number, dd is the day of the month,
-- HHMMSS are the hours, minutes and seconds, respectively, uuuuuu is the
-- number of microseconds, and +ooo is the offset from UTC in minutes. If east
-- of UTC, the number is preceded by a plus (+) sign, and if west of UTC, the
-- number is preceded by a minus (-) sign.
--
-- For example, Wednesday, May 25, 1994, at 1:30:15 PM EDT
--   would be represented as: 19940525133015.000000-300
--
-- Values must be zero-padded if necessary, like "05" in the example above.
-- If a value is not supplied for a field, each character in the field
-- must be replaced with asterisk ('*') characters.
DellDateName                    ::= DisplayString (SIZE (25))

--
-- Status
--
DellStatus                  ::= INTEGER {
    other(1),               -- status is not one of the following:
    unknown(2),             -- status of object is unknown (not known or monitored)
    ok(3),                  -- status of object is OK (normal)
    nonCritical(4),         -- status of object is noncritical (warning)
    critical(5),            -- status of object is critical (failure)
    nonRecoverable(6)       -- status of object is non-recoverable (dead)
}


-------------------------------------------------------------------------------
--
-- MIB Groups
--
-------------------------------------------------------------------------------


-------------------------------------------------------------------------------
-- Field Replaceable Unit (FRU) Group
--
-- OID: 1.3.6.1.4.1.674.10892.1.2000
-------------------------------------------------------------------------------


-------------------------------------------------------------------------------
-- Field Replaceable Unit (FRU) Table
--
-- OID Format: 1.3.6.1.4.1.674.10892.1.2000.10.1.<a>.<i1>.<i2>
-------------------------------------------------------------------------------

DellFRUInformationState                         ::= INTEGER {
    ok(1),                                      -- FRU information is OK
    notSupported(2),                            -- FRU information is not supported
    notAvailable(3),                            -- FRU information is not available
    checksumInvalid(4),                         -- FRU information checksum is invalid
    corrupted(5)                                -- FRU information is corrupted
}

FruTableEntry                                   ::= SEQUENCE {
    fruChassisIndex                             DellObjectRange,
    fruIndex                                    DellObjectRange,
    fruInformationStatus                        DellStatus,
    fruInformationState                         DellFRUInformationState,
    fruDeviceName                               DisplayString (SIZE (0..64)),
    fruManufacturerName                         DisplayString (SIZE (0..64)),
    fruSerialNumberName                         DisplayString (SIZE (0..64)),
    fruPartNumberName                           DisplayString (SIZE (0..64)),
    fruRevisionName                             DisplayString (SIZE (0..64)),
    fruManufacturingDateName                    DellDateName,
    fruAssetTagName                             DisplayString (SIZE (0..64))
}

fruTable                                        OBJECT-TYPE
    SYNTAX      SEQUENCE OF FruTableEntry
    ACCESS      not-accessible
    STATUS      mandatory
    DESCRIPTION
"2000.0010 This object defines the Field Replaceable Unit table."
    ::= { fruGroup 10 }
fruTableEntry                                   OBJECT-TYPE
    SYNTAX      FruTableEntry
    ACCESS      not-accessible
    STATUS      mandatory
    DESCRIPTION
"2000.0010.0001 This object defines the Field Replaceable Unit table entry."
    INDEX       { fruChassisIndex,
                  fruIndex }
    ::= { fruTable 1 }

fruChassisIndex                                 OBJECT-TYPE
    SYNTAX      DellObjectRange
    ACCESS      read-only
    STATUS      mandatory
    DESCRIPTION
"2000.0010.0001.0001 This attribute defines the index (one based) of the
chassis containing the field replaceable unit."
    ::= { fruTableEntry 1 }
fruIndex                                        OBJECT-TYPE
    SYNTAX      DellObjectRange
    ACCESS      read-only
    STATUS      mandatory
    DESCRIPTION
"2000.0010.0001.0002 This attribute defines the index (one based) of the
field replaceable unit."
    ::= { fruTableEntry 2 }
fruInformationStatus                            OBJECT-TYPE
    SYNTAX      DellStatus
    ACCESS      read-only
    STATUS      mandatory
    DESCRIPTION
"2000.0010.0001.0003 This attribute defines the status of the
field replaceable unit information."
    ::= { fruTableEntry 3 }
fruInformationState                             OBJECT-TYPE
    SYNTAX      DellFRUInformationState
    ACCESS      read-only
    STATUS      mandatory
    DESCRIPTION
"2000.0010.0001.0004 This attribute defines the state of the
field replaceable unit information.  Some information for the
field replaceable unit may not be available if the state is
other than ok(1)."
    ::= { fruTableEntry 4 }
fruDeviceName                                   OBJECT-TYPE
    SYNTAX      DisplayString (SIZE (0..64))
    ACCESS      read-only
    STATUS      mandatory
    DESCRIPTION
"2000.0010.0001.0005 This attribute defines the device name of the
field replaceable unit."
    ::= { fruTableEntry 5 }
fruManufacturerName                             OBJECT-TYPE
    SYNTAX      DisplayString (SIZE (0..64))
    ACCESS      read-only
    STATUS      mandatory
    DESCRIPTION
"2000.0010.0001.0006 This attribute defines the manufacturer of the
field replaceable unit."
    ::= { fruTableEntry 6 }
fruSerialNumberName                             OBJECT-TYPE
    SYNTAX      DisplayString (SIZE (0..64))
    ACCESS      read-only
    STATUS      mandatory
    DESCRIPTION
"2000.0010.0001.0007 This attribute defines the serial number of the
field replaceable unit."
    ::= { fruTableEntry 7 }
fruPartNumberName                               OBJECT-TYPE
    SYNTAX      DisplayString (SIZE (0..64))
    ACCESS      read-only
    STATUS      mandatory
    DESCRIPTION
"2000.0010.0001.0008 This attribute defines the part number of the
field replaceable unit."
    ::= { fruTableEntry 8 }
fruRevisionName                                 OBJECT-TYPE
    SYNTAX      DisplayString (SIZE (0..64))
    ACCESS      read-only
    STATUS      mandatory
    DESCRIPTION
"2000.0010.0001.0009 This attribute defines the revision of the
field replaceable unit."
    ::= { fruTableEntry 9 }
fruManufacturingDateName                        OBJECT-TYPE
    SYNTAX      DellDateName
    ACCESS      read-only
    STATUS      mandatory
    DESCRIPTION
"2000.0010.0001.0010 This attribute defines the manufacturing date of the
of the field replaceable unit."
    ::= { fruTableEntry 10 }
fruAssetTagName                                 OBJECT-TYPE
    SYNTAX      DisplayString (SIZE (0..64))
    ACCESS      read-only
    STATUS      mandatory
    DESCRIPTION
"2000.0010.0001.0011 This attribute defines the asset tag of the
field replaceable unit."
    ::= { fruTableEntry 11 }


END


-------------------------------------------------------------------------------
-- End MIB
-------------------------------------------------------------------------------
